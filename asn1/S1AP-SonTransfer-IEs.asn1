-- 3GPP TS 36.413 V14.0.0 (2016-09)
-- B.2	ASN.1 definition
-- **************************************************************
--
-- IE definitions for the SON Transfer application
-- The IEs in this ASN.1 module shall be defined and encoded
-- using the same rules as applicable for the S1AP-IEs module.
-- 
-- **************************************************************

S1AP-SonTransfer-IEs

DEFINITIONS AUTOMATIC TAGS ::= 

BEGIN

--
-- Generic IEs for the SON Transfer application
--

SONtransferApplicationIdentity ::= ENUMERATED {
	cell-load-reporting,
	...,
	multi-cell-load-reporting,
	event-triggered-cell-load-reporting,
	ho-reporting,
	eutran-cell-activation,
	energy-savings-indication,
	failure-event-reporting
}

SONtransferRequestContainer ::= CHOICE{
	cellLoadReporting					NULL,
	...,
	multiCellLoadReporting				MultiCellLoadReportingRequest,
	eventTriggeredCellLoadReporting		EventTriggeredCellLoadReportingRequest,
	hOReporting							HOReport,
	eutranCellActivation				CellActivationRequest,
	energySavingsIndication				CellStateIndication,
	failureEventReporting				FailureEventReport
}

SONtransferResponseContainer ::= CHOICE{
	cellLoadReporting					CellLoadReportingResponse,
	...,
	multiCellLoadReporting				MultiCellLoadReportingResponse,
	eventTriggeredCellLoadReporting	EventTriggeredCellLoadReportingResponse,
	hOReporting							NULL,
	eutranCellActivation				CellActivationResponse,
	energySavingsIndication				NULL,
	failureEventReporting				NULL
}

SONtransferCause ::= CHOICE {
	cellLoadReporting					CellLoadReportingCause,
	...,
	multiCellLoadReporting				CellLoadReportingCause,
	eventTriggeredCellLoadReporting		CellLoadReportingCause,
	hOReporting							HOReportingCause,
	eutranCellActivation				CellActivationCause,
	energySavingsIndication				CellStateIndicationCause,
	failureEventReporting				FailureEventReportingCause
}


CellLoadReportingCause ::= ENUMERATED {
	application-container-syntax-error,
	inconsistent-reporting-cell-identifier,
	unspecified,
	...
}

HOReportingCause ::= ENUMERATED {
	application-container-syntax-error,
	inconsistent-reporting-cell-identifier,
	unspecified,
	...
}

CellActivationCause ::= ENUMERATED {
	application-container-syntax-error,
	inconsistent-reporting-cell-identifier,
	unspecified,
	...
}

CellStateIndicationCause ::= ENUMERATED {
	application-container-syntax-error,
	inconsistent-reporting-cell-identifier,
	unspecified,
	...
}

FailureEventReportingCause ::= ENUMERATED {
	application-container-syntax-error,
	inconsistent-reporting-cell-identifier,
	unspecified,
	...
}

--
-- IEs for Cell Load Reporting application
--

CellLoadReportingResponse::= CHOICE{
	eUTRAN			EUTRANcellLoadReportingResponse,
	uTRAN			OCTET STRING,
	gERAN			OCTET STRING,
	...,
	eHRPD			EHRPDSectorLoadReportingResponse
}

CompositeAvailableCapacityGroup ::= OCTET STRING

EUTRANcellLoadReportingResponse ::= SEQUENCE {
	compositeAvailableCapacityGroup		CompositeAvailableCapacityGroup,
	...
}

--
-- IEs for Multi-Cell Load Reporting application
--

EUTRANResponse::= SEQUENCE {
	cell-ID			OCTET STRING,
	eUTRANcellLoadReportingResponse		EUTRANcellLoadReportingResponse,
	...
}

EHRPD-Sector-ID ::= OCTET STRING (SIZE (16))

IRAT-Cell-ID ::= CHOICE{
	eUTRAN			OCTET STRING,
	uTRAN			OCTET STRING,
	gERAN			OCTET STRING,
	...,
	eHRPD			EHRPD-Sector-ID
}

RequestedCellList ::= SEQUENCE (SIZE(1.. maxnoofIRATReportingCells)) OF IRAT-Cell-ID

MultiCellLoadReportingRequest::= SEQUENCE {
	requestedCellList						RequestedCellList,
	...
}

ReportingCellList-Item ::= SEQUENCE {
	cell-ID									IRAT-Cell-ID,
	...
}

ReportingCellList ::= SEQUENCE (SIZE(1.. maxnoofIRATReportingCells)) OF ReportingCellList-Item

MultiCellLoadReportingResponse ::= SEQUENCE (SIZE(1.. maxnoofIRATReportingCells)) OF MultiCellLoadReportingResponse-Item

MultiCellLoadReportingResponse-Item ::= CHOICE{ 
	eUTRANResponse							EUTRANResponse,
	uTRANResponse							OCTET STRING,
	gERANResponse							OCTET STRING,
	...,
	eHRPD									EHRPDMultiSectorLoadReportingResponseItem
}


--
-- IEs for Event-triggered Cell Load Reporting application
--

NumberOfMeasurementReportingLevels ::= ENUMERATED {
	rl2,
	rl3,
	rl4,
	rl5,
	rl10,
	...
}

EventTriggeredCellLoadReportingRequest ::= SEQUENCE {
	numberOfMeasurementReportingLevels		NumberOfMeasurementReportingLevels,
	...
}

OverloadFlag ::= ENUMERATED {
	overload,
	...
}

EventTriggeredCellLoadReportingResponse ::= SEQUENCE {
	cellLoadReportingResponse				CellLoadReportingResponse,
	overloadFlag							OverloadFlag						OPTIONAL,
	...
}

--
-- IEs for HO Reporting application
--



HOReport::= SEQUENCE {
	hoType					HoType,
	hoReportType			HoReportType,
	hosourceID				IRAT-Cell-ID,
	hoTargetID				IRAT-Cell-ID,
	candidateCellList		CandidateCellList,
	...,
	candidatePCIList		CandidatePCIList	OPTIONAL
}

HoType ::= ENUMERATED {
	ltetoutran,
	ltetogeran,
	...
}

HoReportType ::= ENUMERATED {
	unnecessaryhotoanotherrat,
	...,
	earlyirathandover
}

CandidateCellList ::= SEQUENCE (SIZE(1..maxnoofcandidateCells)) OF IRAT-Cell-ID

CandidatePCIList ::= SEQUENCE (SIZE(1..maxnoofcandidateCells)) OF CandidatePCI

CandidatePCI ::= SEQUENCE {
	pCI			INTEGER (0..503),
	eARFCN		OCTET STRING,
	...
}

--
-- IEs for E-UTRAN Cell Activation application
--

CellActivationRequest ::= SEQUENCE {
	cellsToActivateList		CellsToActivateList,
	minimumActivationTime	INTEGER (1..60)		OPTIONAL,
...
}

CellsToActivateList ::= SEQUENCE (SIZE(1.. maxnoofCellineNB)) OF CellsToActivateList-Item

CellsToActivateList-Item ::= SEQUENCE {
	cell-ID					OCTET STRING,
	...
}

CellActivationResponse ::= SEQUENCE {
	activatedCellsList		ActivatedCellsList,
	...
}

ActivatedCellsList ::= SEQUENCE (SIZE(0.. maxnoofCellineNB)) OF ActivatedCellsList-Item

ActivatedCellsList-Item ::= SEQUENCE {
	cell-ID					OCTET STRING,
	...
}

--
-- IEs for Energy Savings Indication application
--

CellStateIndication ::= SEQUENCE {
	notificationCellList			NotificationCellList,
	...
}

NotificationCellList ::= SEQUENCE (SIZE(1.. maxnoofCellineNB)) OF NotificationCellList-Item

NotificationCellList-Item ::= SEQUENCE {
	cell-ID					OCTET STRING,
	notifyFlag				NotifyFlag,
	...
}

NotifyFlag ::= ENUMERATED {
	activated,
	deactivated,
	...
}

FailureEventReport::= CHOICE {
	tooEarlyInterRATHOReportFromEUTRAN			TooEarlyInterRATHOReportReportFromEUTRAN,
	...
}

TooEarlyInterRATHOReportReportFromEUTRAN ::= SEQUENCE {
	uERLFReportContainer	OCTET STRING, -- as defined in TS 36.331 [16] --
	mobilityInformation		MobilityInformation		OPTIONAL,
	...
}

MobilityInformation ::= BIT STRING (SIZE(32))


--
-- IEs for reporting of eHRPD load
--

EHRPDCapacityValue ::= INTEGER (0..100)

EHRPDSectorCapacityClassValue ::= INTEGER (1..100, ...)

EHRPDSectorLoadReportingResponse ::= SEQUENCE {
	dL-EHRPD-CompositeAvailableCapacity			EHRPDCompositeAvailableCapacity,
	uL-EHRPD-CompositeAvailableCapacity			EHRPDCompositeAvailableCapacity,
	...
}

EHRPDCompositeAvailableCapacity ::= SEQUENCE {
	eHRPDSectorCapacityClassValue				EHRPDSectorCapacityClassValue,
	eHRPDCapacityValue							EHRPDCapacityValue,
	...
}

EHRPDMultiSectorLoadReportingResponseItem ::= SEQUENCE {
	eHRPD-Sector-ID							EHRPD-Sector-ID,
	eHRPDSectorLoadReportingResponse		EHRPDSectorLoadReportingResponse,
	...
}


-- **************************************************************
--
-- Constants
--
-- **************************************************************

maxnoofIRATReportingCells					INTEGER ::= 128
maxnoofcandidateCells						INTEGER ::= 16
maxnoofCellineNB							INTEGER ::= 256

END
